--Karayollari NTCIP Protokolu
--****************************************************************************
--NTCIP OBJECTS

TC-KGM-NTCIP DEFINITIONS ::= BEGIN
    --NTCIP 8004 v02 Header
    --
    --For the purpose of this section, the following OBJECT IDENTIFIERS are used:
    IMPORTS
	--NTCIP 1201 ve 1202 eklenmeli @TODO
    OBJECT-TYPE
        FROM RFC1212-MIB
    Counter, null, enterprises
        FROM RFC1155-SMI;

    kgm                                 OBJECT IDENTIFIER ::= { enterprises 59873 }
    kgm_transportation                  OBJECT IDENTIFIER ::= { kgm 4 }
    kgm_devices                         OBJECT IDENTIFIER ::= { kgm_transportation 2 }
    kgm_asc                             OBJECT IDENTIFIER ::= { kgm_devices 1 }

    kgm_moduleErrorStatus               OBJECT IDENTIFIER ::= { kgm_asc 1 }
    kgm_channel                         OBJECT IDENTIFIER ::= { kgm_asc 2 }
    kgm_signalState                     OBJECT IDENTIFIER ::= { kgm_asc 3 }
    kgm_coord                           OBJECT IDENTIFIER ::= { kgm_asc 4 }
    kgm_detector                        OBJECT IDENTIFIER ::= { kgm_asc 5 }
    kgm_user                            OBJECT IDENTIFIER ::= { kgm_asc 6 }

--1.1 kgm_moduleErrorStatus
--1.1.1 kgm_maxDriverModuleGroupStatus
    kgm_maxDriverModuleGroupStatus OBJECT-TYPE 
        SYNTAX              INTEGER (1..255)
        ACCESS              read-only
        STATUS              mandatory
        DESCRIPTION         "<Definition> Maksimum surucu modul grup durum sayisi.  
                            kgm_trafficLightFaultIndex maksimum degerini asamaz. 
                            <Object Identifier> 1.3.6.1.4.1.59873.4.2.1.1.1
                            <Antra Protocol> ANTRA:-REQ:NMES,-NMES:08,03"
        ::= { kgm_moduleErrorStatus 1}
--1.1.2 kgm_driverModuleGroupStatus
    kgm_driverModuleGroupStatus OBJECT-TYPE
        SYNTAX              INTEGER (0..65535)
        ACCESS              read-only
        STATUS              mandatory
        DESCRIPTION         "<Definition>Surucu modulu durum bilgisi yer alir.
		                    Modul grup numarasina gore 16 modul bilgisini icerir.
                            Bit = 0 ise modul calismiyor.
                            Bit = 1 ise modul calisiyor.
                            Bit 15: Module 16
                            Bit 14: Module 15
                            Bit 13: Module 14
                            Bit 12: Module 13
                            Bit 11: Module 12
                            Bit 10: Module 11
                            Bit 9 : Module 10
                            Bit 8 : Module 9
                            Bit 7 : Module 8 
                            Bit 6 : Module 7 
                            Bit 5 : Module 6 
                            Bit 4 : Module 5 
                            Bit 3 : Module 4 
                            Bit 2 : Module 3 
                            Bit 1 : Module 2 
                            Bit 0 : Module 1
                            <Object Identifier>1.3.6.1.4.1.59873.4.2.1.1.2
                            <Antra Protocol> ANTRA:-REQ:NMES,-NMES:08,03"
        ::= { kgm_moduleErrorStatus 2 }

--1.2 kgm_channel
--1.2.1 kgm_maxTrafficLightFaultStatusGroups
    kgm_maxTrafficLightFaultStatusGroups OBJECT-TYPE 
        SYNTAX              INTEGER (0..255)
        ACCESS              read-only
        STATUS              mandatory
        DESCRIPTION         "<Definition>Maksimum kanal ariza durum sayisi. 
                            kgm_trafficLightFaultIndex maksimum degerini alamaz.
                            <Object Identifier> 1.3.6.1.4.1.59873.4.2.1.2.1
                            <Antra Protocol> ANTRA:-REQ:NCHA,-NCHA:08,03"
        ::= { kgm_channel 1}
--1.2.2 kgm_trafficLightFaultStatusTable
    kgm_trafficLightFaultStatusTable OBJECT-TYPE
        SYNTAX              SEQUENCE OF kgm_TrafficLightFaultStatusEntry 
        ACCESS              not-accessible
        STATUS              mandatory
        DESCRIPTION         "<Definition> Lamba grubunun ariza durum tablosu
                            <TableType> static
                            <Object Identifier> 1.3.6.1.4.1.59873.4.2.1.2.2"
        ::= { kgm_channel 2 }
--1.2.2.1 kgm_trafficLightFaultStatusEntry
    kgm_trafficLightFaultStatusEntry OBJECT-TYPE 
        SYNTAX              kgm_TrafficLightFaultStatusEntry 
        ACCESS              not-accessible
        STATUS              mandatory
        DESCRIPTION         "<Definition> Lamba grubunun ariza durum entry'si
                            <Object Identifier> 1.3.6.1.4.1.59873.4.2.1.2.2.1
                            <Unit> "
        INDEX               { kgm_trafficLightFaultIndex }
        ::= {  kgm_trafficLightFaultStatusTable 1 }

    kgm_TrafficLightFaultStatusEntry ::= SEQUENCE { 
        kgm_trafficLightFaultIndex          INTEGER, 
        kgm_trafficLightFaultChannelNumber  INTEGER, 
        kgm_trafficLightFaultGreenStatus    INTEGER, 
        kgm_trafficLightFaultYellowStatus   INTEGER, 
        kgm_trafficLightFaultRedStatus      INTEGER
    }
--1.2.2.1.1 kgm_trafficLightFaultIndex
    kgm_trafficLightFaultIndex OBJECT-TYPE
        SYNTAX              INTEGER (1..255) 
        ACCESS              read-only
        STATUS              mandatory 
        DESCRIPTION         "<Definition> Ariza tablosu id bilgisi
                            <Object Identifier> 1.3.6.1.4.1.59873.4.2.1.2.2.1.1 
                            <Unit> "
        ::= { kgm_trafficLightFaultStatusEntry 1 }
--1.2.2.1.2 kgm_trafficLightFaultChannelNumber
    kgm_trafficLightFaultChannelNumber OBJECT-TYPE
        SYNTAX              INTEGER (1..255)
        ACCESS              read-only
        STATUS              mandatory
        DESCRIPTION         "<Definition> Kanal tablosundaki channelNumber (grup numarasi) bilgisini icerir.
                            <Object Identifier> 1.3.6.1.4.1.59873.4.2.1.2.2.1.2
                            <Unit>"
        ::= { kgm_trafficLightFaultStatusEntry 2 }
--1.2.2.1.3 kgm_trafficLightFaultGreenStatus
    kgm_trafficLightFaultGreenStatus OBJECT-TYPE
        SYNTAX              INTEGER (0..255)
        ACCESS              read-only
        STATUS              mandatory
        DESCRIPTION         "<Definition>
                            1 Byte
                            0: ariza yok
                            Bit 1: Lamba arizasi(Kritik olmayan)
                            Bit 2: Kritik lamba arizasi
                            Bit 3: Tum lamba arizasi
                            Bit 4: Cakisma var
                            Bit 5: Kisa devre arizasi (Sinyal cikis anahtari kisa devre / sinyal grup cikisi kisa devre veya haricen kablo kisa devresi)
                            Bit 6: Sinyal cikis anahtari acik devre / sinyal grup cikisi acik devre
                            Bit 7: Rez.
                            <Object Identifier> 1.3.6.1.4.1.59873.4.2.1.2.2.1.3
                            <Unit>"
        ::= { kgm_trafficLightFaultStatusEntry 3 }
--1.2.2.1.4 kgm_trafficLightFaultYellowStatus
    kgm_trafficLightFaultYellowStatus OBJECT-TYPE
        SYNTAX              INTEGER (0..255)
        ACCESS              read-only
        STATUS              mandatory
        DESCRIPTION         "<Definition>
                            1 Byte
                            Bit 0: ariza yok
                            Bit 1: Lamba arizasi(Kritik olmayan)
                            Bit 2: Kritik lamba arizasi
                            Bit 3: Tum lamba arizasi
                            Bit 4: Cakisma var
                            Bit 5: Kisa devre arizasi (Sinyal cikis anahtari kisa devre / sinyal grup cikisi kisa devre veya haricen kablo kisa devresi)
                            Bit 6: Sinyal cikis anahtari acik devre / sinyal grup cikisi acik devre
                            Bit 7: Rez.
                            <Object Identifier> 1.3.6.1.4.1.59873.4.2.1.2.2.1.4
                            <Unit>"
        ::= { kgm_trafficLightFaultStatusEntry 4 }
--1.2.2.1.5 kgm_trafficLightFaultRedStatus
    kgm_trafficLightFaultRedStatus OBJECT-TYPE
        SYNTAX 				INTEGER (0..255)
        ACCESS 				read-only
        STATUS 				mandatory
        DESCRIPTION         "<Definition>
                            1 Byte
                            Bit 0: ariza yok
                            Bit 1: Lamba arizasi(Kritik olmayan)
                            Bit 2: Kritik lamba arizasi
                            Bit 3: Tum lamba arizasi
                            Bit 4: Cakisma var
                            Bit 5: Kisa devre arizasi (Sinyal cikis anahtari kisa devre / sinyal grup cikisi kisa devre veya haricen kablo kisa devresi)
                            Bit 6: Sinyal cikis anahtari acik devre / sinyal grup cikisi acik devre
                            Bit 7: Rez.
                            <Object Identifier> 1.3.6.1.4.1.59873.4.2.1.2.2.1.5
                            <Unit>"
        ::= { kgm_trafficLightFaultStatusEntry 5 }
--1.2.3 kgm_maxChannelErrorFlagsGroups
    kgm_maxChannelErrorFlagsGroups OBJECT-TYPE
        SYNTAX 				INTEGER (0..255)
        ACCESS 				read-only
        STATUS 				mandatory
        DESCRIPTION         "<Definition>
                            Maksimum kanal ariza durum sayisi. kgm_trafficLightFaultIndex maksimum degerini alamaz.
                            <Object Identifier> 1.3.6.1.4.1.59873.4.2.1.2.3"
        ::= { kgm_channel 3 }
--1.2.4 kgm_channelErrorFlagsTable
    kgm_channelErrorFlagsTable OBJECT-TYPE
        SYNTAX 				SEQUENCE OF kgm_ChannelErrorFlagsEntry
        ACCESS 				not-accessible
        STATUS 				mandatory
        DESCRIPTION         "<Definition> Kanal hata durum bayraklari grup tablosu. 
                            Tabloda ki her bir satir 8li gruplar halinde ifade edilebilecek sekilde organize edilmistir.
                            <Object Identifier> 1.3.6.1.4.1.59873.4.2.1.2.4
                            <Unit> group"
        ::= { kgm_channel 4 }
--1.2.4.1 kgm_channelErrorFlagsEntry
    kgm_channelErrorFlagsEntry OBJECT-TYPE
        SYNTAX 				kgm_ChannelErrorFlagsEntry
        ACCESS 				not-accessible
        STATUS 				mandatory     
        DESCRIPTION         "<Definition> 8li gruplar halinde kanal hata durum bayraklari.
                            <Object Identifier> 1.3.6.1.4.1.59873.4.2.1.2.4.1 "
        INDEX				{ kgm_errorFlagsGroupNumber }
        ::= { kgm_channelErrorFlagsTable 1 }

    kgm_ChannelErrorFlagsEntry ::= SEQUENCE {
        kgm_errorFlagsGroupNumber   INTEGER,
        kgm_redLampAllFailure       INTEGER,
        kgm_greenLampAllFailure     INTEGER,
        kgm_yellowLampAllFailure    INTEGER,
        kgm_undesiredRedSignal      INTEGER,
        kgm_undesiredGreenSignal    INTEGER,
        kgm_undesiredYellowSignal   INTEGER
    }
--1.2.4.1.1 kgm_errorFlagsGroupNumber
    kgm_errorFlagsGroupNumber OBJECT-TYPE 
        SYNTAX              INTEGER (0..255)
        ACCESS              read-only
        STATUS              mandatory
        DESCRIPTION         "<Definition> Ilgili tablo satirinda ki Kanal hata bayraklari grup numarasi.
                            <Object Identifier> 1.3.6.1.4.1.59873.4.2.1.2.4.1.1
                            <Unit>"
        ::= { kgm_channelErrorFlagsEntry 1 }
--1.2.4.1.2 kgm_redLampAllFailure
    kgm_redLampAllFailure OBJECT-TYPE 
        SYNTAX              INTEGER (0..255)
        ACCESS              read-only
        STATUS              mandatory
        DESCRIPTION         "<Definition>
                            Kanal Kirmizi ariza durumlari
                            Bit=1 ise ilgili kanal kopuk flaman arizasi var.
                            Bit=0 ise ilgili kanal arizasi yok.
                            Bit 7: Channel# = (errorgroupNumber * 8) 
                            Bit 6: Channel# = (errorgroupNumber * 8) - 1 
                            Bit 5: Channel# = (errorgroupNumber * 8) - 2 
                            Bit 4: Channel# = (errorgroupNumber * 8) - 3 
                            Bit 3: Channel# = (errorgroupNumber * 8) - 4 
                            Bit 2: Channel# = (errorgroupNumber * 8) - 5 
                            Bit 1: Channel# = (errorgroupNumber * 8) - 6 
                            Bit 0: Channel# = (errorgroupNumber * 8) - 7
                            <Object Identifier> 1.3.6.1.4.1.59873.4.2.1.2.4.1.2
                            <Unit>"
        ::= { kgm_channelErrorFlagsEntry 2 }
--1.2.4.1.3 kgm_greenLampAllFailure
    kgm_greenLampAllFailure OBJECT-TYPE 
        SYNTAX              INTEGER (0..255)
        ACCESS              read-only
        STATUS              mandatory
        DESCRIPTION         "<Definition>
                            Kanal Yesil ariza durumlari
                            Bit=1 ise ilgili kanal kopuk flaman arizasi var.
                            Bit=0 ise ilgili kanal arizasi yok.
                            Bit 7: Channel# = (errorgroupNumber * 8)
                            Bit 6: Channel# = (errorgroupNumber * 8) - 1
                            Bit 5: Channel# = (errorgroupNumber * 8) - 2
                            Bit 4: Channel# = (errorgroupNumber * 8) - 3
                            Bit 3: Channel# = (errorgroupNumber * 8) - 4
                            Bit 2: Channel# = (errorgroupNumber * 8) - 5
                            Bit 1: Channel# = (errorgroupNumber * 8) - 6 
                            Bit 0: Channel# = (errorgroupNumber * 8) - 7
                            <Object Identifier> 1.3.6.1.4.1.59873.4.2.1.2.4.1.3
                            <Unit>  "
        ::= { kgm_channelErrorFlagsEntry 3 }
--1.2.4.1.4 kgm_yellowLampAllFailure
    kgm_yellowLampAllFailure OBJECT-TYPE 
        SYNTAX              INTEGER (0..255)
        ACCESS              read-only
        STATUS              mandatory
        DESCRIPTION         "<Definition>
                            Kanal Sari ariza durumlari
                            Bit=1 ise ilgili kanalda kopuk flaman arizasi var. 
                            Bit=0 ise ilgili kanal arizasi yok.
                            Bit 7: Channel# = (errorgroupNumber * 8) 
                            Bit 6: Channel# = (errorgroupNumber * 8) - 1
                            Bit 5: Channel# = (errorgroupNumber * 8) - 2
                            Bit 4: Channel# = (errorgroupNumber * 8) - 3
                            Bit 3: Channel# = (errorgroupNumber * 8) - 4
                            Bit 2: Channel# = (errorgroupNumber * 8) - 5
                            Bit 1: Channel# = (errorgroupNumber * 8) - 6
                            Bit 0: Channel# = (errorgroupNumber * 8) - 7
                            <Object Identifier> 1.3.6.1.4.1.59873.4.2.1.2.4.1.4
                            <Unit>  "
        ::= { kgm_channelErrorFlagsEntry 4 }
--1.2.4.1.5 kgm_undesiredRedSignal
    kgm_undesiredRedSignal OBJECT-TYPE 
        SYNTAX              INTEGER (0..255)
        ACCESS              read-only
        STATUS              mandatory
        DESCRIPTION         "<Definition>
                            Kanal Istemsiz Kirmizi sinyal durumlari
                            Bit=1 ise ilgili kanalda kopuk flaman arizasi var. 
                            Bit=0 ise ilgili kanal arizasi yok.
                            Bit 7: Channel# = (errorgroupNumber * 8) 
                            Bit 6: Channel# = (errorgroupNumber * 8) - 1
                            Bit 5: Channel# = (errorgroupNumber * 8) - 2
                            Bit 4: Channel# = (errorgroupNumber * 8) - 3
                            Bit 3: Channel# = (errorgroupNumber * 8) - 4
                            Bit 2: Channel# = (errorgroupNumber * 8) - 5
                            Bit 1: Channel# = (errorgroupNumber * 8) - 6
                            Bit 0: Channel# = (errorgroupNumber * 8) - 7
                            <Object Identifier> 1.3.6.1.4.1.59873.4.2.1.2.4.1.5
                            <Unit>  "
        ::= { kgm_channelErrorFlagsEntry 5 }
--1.2.4.1.6 kgm_undesiredGreenSignal
    kgm_undesiredGreenSignal OBJECT-TYPE 
        SYNTAX              INTEGER (0..255)
        ACCESS              read-only
        STATUS              mandatory
        DESCRIPTION         "<Definition>
                            Kanal Istemsiz yesil sinyal durumlari
                            Bit=1 ise ilgili kanalda istemsiz sinyal vardir.
                            Bit=0 ise ilgili kanalda istemsiz sinyal yoktur.
                            Bit 7: Channel# = (errorgroupNumber * 8)
                            Bit 6: Channel# = (errorgroupNumber * 8) - 1
                            Bit 5: Channel# = (errorgroupNumber * 8) - 2
                            Bit 4: Channel# = (errorgroupNumber * 8) - 3
                            Bit 3: Channel# = (errorgroupNumber * 8) - 4
                            Bit 2: Channel# = (errorgroupNumber * 8) - 5
                            Bit 1: Channel# = (errorgroupNumber * 8) - 6
                            Bit 0: Channel# = (errorgroupNumber * 8) - 7
                            <Object Identifier> 1.3.6.1.4.1.59873.4.2.1.2.4.1.6
                            <Unit>  "
        ::= { kgm_channelErrorFlagsEntry 6 }
--1.2.4.1.7 kgm_undesiredYellowSignal
    kgm_undesiredYellowSignal  OBJECT-TYPE
        SYNTAX              INTEGER (0..255)
        ACCESS              read-only
        STATUS              mandatory
        DESCRIPTION         "<Definition> 
                            Kanal Istemsiz sari sinyal durumlari
                            Bit=1 ise ilgili kanalda istemsiz sinyal vardir.
                            Bit=0 ise ilgili kanalda istemsiz sinyal yoktur.
                            Bit 7: Channel# = (errorgroupNumber * 8)
                            Bit 6: Channel# = (errorgroupNumber * 8) - 1
                            Bit 5: Channel# = (errorgroupNumber * 8) - 2
                            Bit 4: Channel# = (errorgroupNumber * 8) - 3
                            Bit 3: Channel# = (errorgroupNumber * 8) - 4
                            Bit 2: Channel# = (errorgroupNumber * 8) - 5
                            Bit 1: Channel# = (errorgroupNumber * 8) - 6
                            Bit 0: Channel# = (errorgroupNumber * 8) - 7
                            <Object Identifier> 1.3.6.1.4.1.59873.4.2.1.2.4.1.7
                            <Unit>  "
        ::= { kgm_channelErrorFlagsEntry 7 }

--1.3 kgm_signalState
--1.3.1 kgm_maxSignalState
    kgm_maxSignalState OBJECT-TYPE
        SYNTAX              INTEGER (1..255)
        ACCESS              read-only
        STATUS              mandatory
        DESCRIPTION         "<Definition> 
                            Maksimum sinyal durum sayisina esittir. kgm_signalStateIndex maksimum degerini asamaz
                            <Object Identifier> 1.3.6.1.4.1.59873.4.2.1.3.1"
        ::= { kgm_signalState 1 }
--1.3.2 kgm_signalStateTable
    kgm_signalStateTable OBJECT-TYPE
        SYNTAX              SEQUENCE OF kgm_SignalStateEntry
        ACCESS              not-accessible
        STATUS              mandatory
        DESCRIPTION         "<Definition> Sinyal durum tablosu 
                            <TableType> static
                            <Object Identifier> 1.3.6.1.4.1.59873.4.2.1.3.2"
        ::= { kgm_signalState 2 }
--1.3.2.1 kgm_signalStateEntry
    kgm_signalStateEntry OBJECT-TYPE
        SYNTAX              kgm_SignalStateEntry
        ACCESS              not-accessible
        STATUS              mandatory
        DESCRIPTION         "<Definition> Sinyal durum tablo Entry?si   
                            <Object Identifier> 1.3.6.1.4.1.59873.4.2.1.3.2.1
                            <Unit> " 
        INDEX               { kgm_signalStateIndex }
        ::= {  kgm_signalStateTable 1 }

    kgm_SignalStateEntry ::= SEQUENCE {
        kgm_signalStateIndex                INTEGER,
        kgm_signalStatePatternNo            INTEGER,
        kgm_signalStateExecMode	            INTEGER,
        kgm_signalStatePlanMode	            INTEGER,
        kgm_signalStateStructure            INTEGER,
        kgm_signalStatePlan                 INTEGER,
        kgm_signalStatePhase                OCTET STRING,
        kgm_signalStateNextPhase	        OCTET STRING,
        kgm_signalStateStep	                INTEGER,
        kgm_signalStateTransitionFlag	    INTEGER,
        kgm_signalStateTransitionStep	    INTEGER,
        kgm_signalStateElapsedTime          OCTET STRING,
        kgm_signalStateRemainingTime	    OCTET STRING,
        kgm_signalStateStepTime	            INTEGER,
        kgm_signalStateCycleTime	        INTEGER,
        kgm_patternTimeToNextCycle          INTEGER,
        kgm_signalPlanLastChangeTime        Counter 
    } 
--1.3.2.1.1 kgm_signalStateIndex
    kgm_signalStateIndex OBJECT-TYPE
        SYNTAX              INTEGER (1..255)
        ACCESS              read-only
        STATUS              mandatory
        DESCRIPTION         "<Definition> Sinyal durum tablosu 
                            id bilgisi
                            <Object Identifier> 1.3.6.1.4.1.59873.4.2.1.3.2.1.1
                            <Unit>  "
        ::= { kgm_signalStateEntry 1 }
--1.3.2.1.2 kgm_signalStatePatternNo
    kgm_signalStatePatternNo OBJECT-TYPE
        SYNTAX              INTEGER (1..255)
        ACCESS              read-only
        STATUS              mandatory
        DESCRIPTION         "<Definition> Sinyal durum tablosu 
                            patern numara bilgisi. 
                            <Object Identifier> 1.3.6.1.4.1.59873.4.2.1.3.2.1.2
                            <Unit>  "
        ::= { kgm_signalStateEntry 2 } 
--1.3.2.1.3 kgm_signalStateExecMode
    kgm_signalStateExecMode OBJECT-TYPE
        SYNTAX              INTEGER {
                                none (0),
                                init(1),
                                initialFlash(2),
                                program(3),
                                flash(4),
                                failFlash(5),
                                allYellow(6),
                                allRed(7),
                                allDark(8),
                                testOutputs(9),
                                programError(10),
                                testSignalPlan(11) 
                            } 
        ACCESS              read-only
        STATUS              mandatory
        DESCRIPTION         "<Definition> Hangi modda oldugu bilgisini icerir.
                            Cihaz program modunda ise detayda hangi modda calistigi bilgisi kgm_signalStatePlanMode nesnesinden okunur.
                            None (0)
                            Init(1): Cihaz yeni acildi henuz cikislari surmeye baslamadi
                            InitialFlash(2): Cihaz yeni acilmis veya yapi degisikligi olmus ve baslangic flasi yapiyor.
                            Program(3): Cihaz haftalik plandaki duzene gore calisiyor.
                            Flash(4): Cihaz flas moduna zorlanmis
                            FailFlash(5): Cihaz arizi bir durumdan dolayi flas moduna gecmis
                            AllYellow(6): Tum cikislar sari
                            AllRed(7): Tum cikislar kirmizi
                            AllDark(8): Tum cikislar sonuk
                            TestOutputs(9): cikislarin lambalara dogru bir sekilde baglanip baglanmadigini kontrol 
                                etmek icin sira ile her bir cikisa yesil, sari, kirmizi, kirmizi sari renklerinin verilmesidir.
                            ProgramError(10): Sinyal programcisi tarafindan yuklenen sinyal planinda bir hata olmasi durumunda gecilen mod.
                            TestSignalPlan(11): Bu modda sinyal cikislari kapalidir. Diger her sey program modunda calismaktadir. 
                            <Object Identifier> 1.3.6.1.4.1.59873.4.2.1.3.2.1.3
                            <Unit>  "
        ::= { kgm_signalStateEntry 3 }
--1.3.2.1.4 kgm_signalStatePlanMode
    kgm_signalStatePlanMode OBJECT-TYPE
        SYNTAX              INTEGER {
                                fixedPlan(0),
                                halfActuated(1),
                                fullyActuated(2),
                                centralAdaptive(3),
                                flashing(4),
                                dark(5),
                                localAdaptive(6),
                            }
        ACCESS              read-only
        STATUS              mandatory
        DESCRIPTION         "<Definition> 
                            FixedPlan(0): Multi Plan(sabit sureli), sensorler devre disidir. 
                                Faz sureleri haftalik planda belirlenen surelere gore degismektedir.
                            HalfActuated(1): Kavsagin bazi kollarinda sensor bulunmakta(loop dedektor, 
                                yaya butonu vb.) bazi kollarinda ise sensor bulunmayabilmektedir. Sinyal planindaki bazi 
                                fazlar istenirse pas gecilebilmektedir.
                            FullyActuated(2): Kavsagin butun kollarinda sensor bulunmaktadir. Sinyal planindaki butun fazlar acilmakta ve talep olmasi durumunda max sureye kadar calistirilmaktadir.
                            CentralAdaptive(3): Bu modda plan sureleri merkezi bir program tarafindan uretilmekte ve cihaz tarafindan uygulanmaktadir.
                            Flashing(4): Flasli calisma(Gece flasi gibi)
                            Dark(5): Cikislarin kapali oldugu mod(Sadece belli saatlerde isletilen kavsaklarin olmasi durumu)
                            LocalAdaptive(6): Bu modda plan sureleri lokalde cihaz tarafindan uretilmekte ve uygulanmaktadir.
                            <Object Identifier> 1.3.6.1.4.1.59873.4.2.1.3.2.1.4
                            <Unit>  "
        ::= { kgm_signalStateEntry 4 }
--1.3.2.1.5 kgm_signalStateStructure
    kgm_signalStateStructure OBJECT-TYPE
        SYNTAX              INTEGER (1..255)
        ACCESS              read-only
        STATUS              mandatory
        DESCRIPTION         "<Definition>Calismakta olan yapi numarasi.
                            <Object Identifier> 1.3.6.1.4.1.59873.4.2.1.3.2.1.5
                            <Unit>  "
        ::= { kgm_signalStateEntry 5 }
--1.3.2.1.6 kgm_signalStatePlan
    kgm_signalStatePlan OBJECT-TYPE
        SYNTAX              INTEGER (1..255)
        ACCESS              read-only
        STATUS              mandatory
        DESCRIPTION         "<Definition>Calismakta olan plan numarasi.
                            <Object Identifier> 1.3.6.1.4.1.59873.4.2.1.3.2.1.6
                            <Unit>  "
        ::= { kgm_signalStateEntry 6 }
--1.3.2.1.7 kgm_signalStatePhase
    kgm_signalStatePhase OBJECT-TYPE
        SYNTAX              OCTET STRING
        ACCESS              read-only
        STATUS              mandatory
        DESCRIPTION         "<Definition>  
                            Turkiyedeki faza karsiliktir.
                            Calismakta olan faz veya fazlar.
                            <Object Identifier> 1.3.6.1.4.1.59873.4.2.1.3.2.1.7
                            <Unit>  phase"
        ::= { kgm_signalStateEntry 7 }
--1.3.2.1.8 kgm_signalStateIndex
    kgm_signalStateNextPhase OBJECT-TYPE
        SYNTAX              OCTET STRING
        ACCESS              read-only
        STATUS              mandatory
        DESCRIPTION         "<Definition>   
                            Bir sonraki fazi veya fazlari ifade eder.
                            <Object Identifier> 1.3.6.1.4.1.59873.4.2.1.3.2.1.8
                            <Unit>  phase"
    ::= { kgm_signalStateEntry 8 }
--1.3.2.1.9 kgm_signalStateStep
    kgm_signalStateStep OBJECT-TYPE
        SYNTAX              INTEGER (1..255)
        ACCESS              read-only
        STATUS              mandatory
        DESCRIPTION         "<Definition>Calismakta olan adim
                            0 yada 255  = Uygulanamaz
                            <Object Identifier> 1.3.6.1.4.1.59873.4.2.1.3.2.1.9 
                            <Unit> step "
    ::= { kgm_signalStateEntry 9 }
--1.3.2.1.10 kgm_signalStateTransitionFlag
    kgm_signalStateTransitionFlag OBJECT-TYPE
        SYNTAX              INTEGER (0..1)
        ACCESS              read-only
        STATUS              mandatory
        DESCRIPTION         "<Definition>Calismakta olan adimin gecis adimi olup olmadigi bilgisini icerir.
                            <Object Identifier> 1.3.6.1.4.1.59873.4.2.1.3.2.1.10
                            <Unit>  flag"
        ::= { kgm_signalStateEntry 10 }
--1.3.2.1.11 kgm_signalStateTransitionStep
    kgm_signalStateTransitionStep OBJECT-TYPE
        SYNTAX              INTEGER (0..255)
        ACCESS              read-only
        STATUS              mandatory
        DESCRIPTION         "<Definition>Gecis adimi numarasi
                            <Object Identifier> 1.3.6.1.4.1.59873.4.2.1.3.2.1.11
                            <Unit>  step"
        ::= { kgm_signalStateEntry 11 }
--1.3.2.1.12 kgm_signalStateElapsedTime
    kgm_signalStateElapsedTime OBJECT-TYPE
        SYNTAX              OCTET STRING
        ACCESS              read-only
        STATUS              mandatory
        DESCRIPTION         "<Definition> Mevcut adim veya adimlarin basladigi andan itibaren gecen sure 
                            <Object Identifier> 1.3.6.1.4.1.59873.4.2.1.3.2.1.12 
                            <Unit>  second"
        ::= { kgm_signalStateEntry 12 }
--1.3.2.1.13 kgm_signalStateRemainingTime
    kgm_signalStateRemainingTime OBJECT-TYPE
        SYNTAX              OCTET STRING
        ACCESS              read-only
        STATUS              mandatory
        DESCRIPTION         "<Definition> Mevcut adim veya adimlarin kalan suresi 
                            <Object Identifier> 1.3.6.1.4.1.59873.4.2.1.3.2.1.13
                            <Unit>  second"
        ::= { kgm_signalStateEntry 13 }
--1.3.2.1.14 kgm_signalStateStepTime
    kgm_signalStateStepTime OBJECT-TYPE
        SYNTAX              INTEGER (0..255)
        ACCESS              read-only
        STATUS              mandatory
        DESCRIPTION         "<Definition> Adimin toplam suresi
                            0 yada 255  = Uygulanamaz
                            <Object Identifier> 1.3.6.1.4.1.59873.4.2.1.3.2.1.14
                            <Unit> second"
        ::= { kgm_signalStateEntry 14 }
--1.3.2.1.15 kgm_signalStateCycleTime
    kgm_signalStateCycleTime OBJECT-TYPE
        SYNTAX              INTEGER (0..255)
        ACCESS              read-only
        STATUS              mandatory
        DESCRIPTION         "<Definition>  
                            Devre suresi
                            <Object Identifier> 1.3.6.1.4.1.59873.4.2.1.3.2.1.15
                            <Unit>  second"
        ::= { kgm_signalStateEntry 15 }
--1.3.2.1.16 kgm_patternTimeToNextCycle
    kgm_patternTimeToNextCycle OBJECT-TYPE
        SYNTAX              INTEGER (0..255)
        ACCESS              read-only
        STATUS              mandatory
        DESCRIPTION         "<Definition> Yesil dalga durumunda sonraki peryodun baslangicina kalan sure(sn).
                            <Object Identifier> 1.3.6.1.4.1.59873.4.2.1.3.2.1.16
                            <Unit> second"
        ::= { kgm_signalStateEntry 16 }
--1.3.3 kgm_signalPlanLastChangeTime
    kgm_signalPlanLastChangeTime OBJECT-TYPE
        SYNTAX              Counter (0..4294967295)
        ACCESS              read-only
        STATUS              mandatory
        DESCRIPTION         "<Definition> Sinyal planinin son degistirildigi zaman bilgisi 
                            <Object Identifier> 1.3.6.1.4.1.59873.4.2.1.3.3
                            <Unit> second"
        ::= {  kgm_signalState 3 }
--1.4 kgm_Coord
--1.4.1 kgm_maxTrPattern
    kgm_maxTrPattern OBJECT-TYPE
        SYNTAX              INTEGER (1..255)
        ACCESS              read-only
        STATUS              mandatory
        DESCRIPTION         "<Definition>Maksimum pattern sayisina esittir. kgm_patternIndex maksimum degerini asamaz
                            <Object Identifier> 1.3.6.1.4.1.59873.4.2.1.4.1"
        ::= { kgm_coord 1 }
--1.4.2 kgm_trPatternTable
    kgm_trPatternTable	OBJECT-TYPE
        SYNTAX              SEQUENCE OF kgm_trPatternEntry
        ACCESS              not-accessible
        STATUS              mandatory
        DESCRIPTION         "<Definition><TableType> static
                            <Object Identifier> 1.3.6.1.4.1.59873.4.2.1.4.2"
        ::= { kgm_coord 2 }
--1.4.2.1 kgm_trPatternEntry
    kgm_trPatternEntry OBJECT-TYPE
        SYNTAX              kgm_trPatternEntry
        ACCESS              not-accessible
        STATUS              mandatory
        DESCRIPTION         "<Definition>
                            <Object Identifier> 1.3.6.1.4.1.59873.4.2.1.4.2.1
                            <Unit> "
        INDEX { kgm_patternNo }
        ::= {  kgm_trPatternTable 1 }

    kgm_trPatternEntry::= SEQUENCE {
        kgm_patternNo INTEGER,
		kgm_patternPriority INTEGER, 
		kgm_patternPlanMode INTEGER,
		kgm_patternExtendedMode INTEGER,
		kgm_patternSequenceNumber INTEGER, 
		kgm_patternSplitNumber INTEGER,
		kgm_patternCoordStatus INTEGER, 
		kgm_patternOutputSupervision INTEGER,
		kgm_patternSpecialParameterTableIndex INTEGER,
    }
--1.4.2.1.1 kgm_patternNo
    kgm_patternNo OBJECT-TYPE
        SYNTAX              INTEGER (1..255)
        ACCESS              read-only
        STATUS              mandatory
        DESCRIPTION         "<Definition> 
                            <Object Identifier> 1.3.6.1.4.1.59873.4.2.1.4.2.1.1
                            <Unit>  "
        ::= { kgm_trPatternEntry 1 }
--1.4.2.1.2 kgm_patternPriority
    kgm_patternPriority OBJECT-TYPE
        SYNTAX              INTEGER (1..255)
        ACCESS              read-only
        STATUS              mandatory
        DESCRIPTION         "<Definition> 
                            <Object Identifier> 1.3.6.1.4.1.59873.4.2.1.4.2.1.2
                            <Unit> pattern"
        ::= { kgm_trPatternEntry 2 }
--1.4.2.1.3 kgm_patternPlanMode
    kgm_patternPlanMode OBJECT-TYPE
        SYNTAX              INTEGER {
                                fixedPlan(0),
                                halfActuated(1),
                                fullyActuated(2),
                                centralAdaptive(3),
                                flashing(4),
                                dark(5) 
                            }
            ACCESS          read-only
            STATUS          mandatory
            DESCRIPTION     "<Definition> 
                                FixedPlan(0): Multi Plan(sabit sureli), sensorler devre disidir. 
                                    Faz sureleri haftalik planda belirlenen surelere gore degismektedir.
                                HalfActuated(1): Kavsagin bazi kollarinda sensor bulunmakta(loop dedektor, yaya butonu vb.) 
                                    bazi kollarinda ise sensor bulunmayabilmektedir. Sinyal planindaki bazi fazlar istenirse 
                                    pas gecilebilmektedir.
                                FullyActuated(2): Kavsagin butun kollarinda sensor bulunmaktadir. Sinyal planindaki butun 
                                    fazlar acilmakta ve talep olmasi durumunda max sureye kadar calistirilmaktadir.
                                CentralAdaptive(3): Bu modda plan sureleri merkezi bir program tarafindan uretilmekte ve 
                                    cihaz tarafindan uygulanmaktadir.
                                Flashing(4): Flasli calisma(Gece flasi gibi)
                                Dark(5): Cikislarin kapali oldugu mod(Sadece belli saatlerde isletilen kavsaklarin olmasi durumu)
                            <Object Identifier> 1.3.6.1.4.1.59873.4.2.1.4.2.1.3
                            <Unit>  "
        ::= { kgm_trPatternEntry 3 }
--1.4.2.1.4 kgm_patternExtendedMode
	kgm_patternExtendedMode OBJECT-TYPE
		SYNTAX              INTEGER (1…255)
		ACCESS              read-only
		STATUS              mandatory
		DESCRIPTION         "<Definition>
							Hangi ek çalışma modlarının desteklendiği ayrıntısı için, üretici cihaz manueline basvurulur. 
							<Object Identifier> 1.3.6.1.4.1.59873.4.2.1.4.2.1.5
							<Unit>  "
		::= { kgm_trPatternEntry 4 }
--1.4.2.1.5 kgm_patternSequenceNumber
    kgm_patternSequenceNumber OBJECT-TYPE
        SYNTAX              OCTET STRING
        ACCESS              read-only
        STATUS              mandatory
        DESCRIPTION         "<Definition> 
                            <Object Identifier> 1.3.6.1.4.1.59873.4.2.1.4.2.1.6
                            <Unit>  "
        ::= { kgm_trPatternEntry 5 }
--1.4.2.1.6 kgm_patternSplitNumber
    kgm_patternSplitNumber OBJECT-TYPE
        SYNTAX              INTEGER (0..255)
        ACCESS              read-
        STATUS              mandatory
        DESCRIPTION         "<Definition> 
                            <Object Identifier> 1.3.6.1.4.1.59873.4.2.1.4.2.1.6
                            <Unit> "
        ::= { kgm_trPatternEntry 6 }
--1.4.2.1.7 kgm_patternCoordStatus
    kgm_patternCoordStatus OBJECT-TYPE
        SYNTAX              INTEGER (0..255)
        ACCESS              read-write
        STATUS              mandatory
        DESCRIPTION         "<Definition> 
                            <Object Identifier> 1.3.6.1.4.1.59873.4.2.1.4.2.1.7
                            <Unit>  plan"
        ::= { kgm_trPatternEntry 7 }
--1.4.2.1.8 kgm_patternOutputSupervision
    kgm_patternOutputSupervision OBJECT-TYPE
        SYNTAX              INTEGER (0..255)
        ACCESS              read-write
        STATUS              mandatory
        DESCRIPTION         "<Definition> Sinyal cikislari ariza kontrolunu devreye almak veya devre disi birakmak icin kullanilir.
                                0: Devre disi
                                1: Devrede
                                2: Degisiklik yok.
                            <Object Identifier> 1.3.6.1.4.1.59873.4.2.1.4.2.1.8
                            <Unit>  "
    ::= { kgm_trPatternEntry 8 } 
--1.4.2.1.9 kgm_patternSpecialParameterTableIndex
    kgm_patternSpecialParameterTableIndex OBJECT-TYPE
        SYNTAX              INTEGER (0..255)
        ACCESS              read-write
        STATUS              mandatory
        DESCRIPTION         "<Definition> 
                            <Object Identifier> 1.3.6.1.4.1.59873.4.2.1.4.2.1.9
                            <Unit>  "
    ::= { kgm_trPatternEntry 9 } 
--1.4.3 kgm_signalPlanUpgrade
    kgm_signalPlanUpgrade OBJECT-TYPE
        SYNTAX              INTEGER (0..1)
        ACCESS              read-only
        STATUS              mandatory
        DESCRIPTION         "<Definition> Sinyal planini devreye alir. 
                            <Object Identifier> 1.3.6.1.4.1.59873.4.2.1.4.3"
    ::= {  kgm_coord 3 }
    
--1.5 kgm_detector
--1.5.1 kgm_dedectorModuleStatus
    kgm_dedectorModuleStatus   OBJECT-TYPE
        SYNTAX              INTEGER (0..65535)
        ACCESS              read-only
        STATUS              mandatory
        DESCRIPTION         "<Definition> Dedektor modulu durum bilgisi yer alir.
                                Dedektor modulu grup numarasina gore 16 modul bilgisini icerir.
                                Bit = 0 ise modul calismiyor.
                                Bit = 1 ise modul calisiyor.
                                Bit 15: Module 16
                                Bit 14: Module 15
                                Bit 13: Module 14
                                Bit 12: Module 13
                                Bit 11: Module 12
                                Bit 10: Module 11
                                Bit 9 : Module 10
                                Bit 8 : Module 9
                                Bit 7 : Module 8
                                Bit 6 : Module 7
                                Bit 5 : Module 6
                                Bit 4 : Module 5
                                Bit 3 : Module 4
                                Bit 2 : Module 3
                                Bit 1 : Module 2
                                Bit 0 : Module 1
                            <Object Identifier> 1.3.6.1.4.1.59873.4.2.1.5.1
                            <Unit>  "
        ::= { kgm_detector 1 }

--1.6 kgm_user
--1.6.1 kgm_maxUserOperations
    kgm_maxUserOperations OBJECT-TYPE
        SYNTAX              INTEGER (1..255)
        ACCESS              read-only
        STATUS              mandatory
        DESCRIPTION         "<Definition> Maksimum kullanici islem sayisina esittir. userOperationsIndex maksimum degerini asamaz
                            <Object Identifier> 1.3.6.1.4.1.59873.4.2.1.6.1"
        ::= { kgm_user 1 }
--1.6.2 kgm_userOperationsTable
    kgm_userOperationsTable OBJECT-TYPE
        SYNTAX              SEQUENCE OF kgm_UserOperationsEntry
        ACCESS              not-accessible
        STATUS              mandatory
        DESCRIPTION         "<Definition> Kullanici islemleri bilgilendirme tablosudur
                            <TableType> static
                            <Object Identifier> 1.3.6.1.4.1.59873.4.2.1.6.2"
        ::= { kgm_user 2 }
--1.6.2.1 kgm_userOperationsEntry
    kgm_userOperationsEntry		OBJECT-TYPE
        SYNTAX              kgm_UserOperationsEntry
        ACCESS              not-accessible
        STATUS              mandatory
    DESCRIPTION             "<Definition> Kullaici islemleri Entry?si   
                            <Object Identifier> 1.3.6.1.4.1.59873.4.2.1.6.2.1
                            <Unit> " 
    INDEX                   { kgm_userOperationsIndex }
    ::= {  kgm_userOperationsTable 1 }

    kgm_UserOperationsEntry ::= SEQUENCE {
        kgm_userOperationsIndex     	INTEGER,
        kgm_userOperationsType      	INTEGER,
        kgm_userOperationsTime      	Counter,
        kgm_userOperationsULoginName 	OCTET STRING
    }
--1.6.2.1.1 kgm_userOperationsIndex
    kgm_userOperationsIndex OBJECT-TYPE
        SYNTAX              INTEGER (1..255)
        ACCESS              read-only
        STATUS              mandatory
        DESCRIPTION         "<Definition> Kullanici islem tablo id bilgisi
                            <Object Identifier> 1.3.6.1.4.1.59873.4.2.1.6.2.1.1
                            <Unit>  "
        ::= { kgm_userOperationsEntry 1 }
--1.6.2.1.2 kgm_userOperationsType
    kgm_userOperationsType OBJECT-TYPE
        SYNTAX              INTEGER { 
                                none(0),
                                userAdded(1),
                                timeChanged(2),
                                outputRelaysEnabled(3),
                                outputRelaysDisabled(4),
                                userLogin(5),
                                userLogout(6),
                                modeChanged(7),
                                deviceParamatersChanged(8)        
                            }	
        ACCESS              read-only
        STATUS              mandatory
        DESCRIPTION         "<Definition> 
                                userAdded: Kullanici eklendi
                                timeChanged: Kullanici tarih saat degistirdi
                                outputRelaysEnabled: Cikis rolesi devrede
                                outputRelaysDisabled: Cikis rolesi devre disi
                                userLogin: Kullanici sisteme giris yapti
                                userLogout: Kullanici sistemden cikis yapti
                                modeChanged: kullanici tarafindan mod degistirildi.
                                deviceParamatersChanged: cihaz paramatreleri degistirildi.
                            <Object Identifier> 1.3.6.1.4.1.59873.4.2.1.6.2.1.2
                            <Unit> "
        ::= { kgm_userOperationsEntry 2} 
--1.6.2.1.3 kgm_userOperationsTime
    kgm_userOperationsTime OBJECT-TYPE
        SYNTAX              Counter (0..4294967295)
        ACCESS              read-only
        STATUS              mandatory
        DESCRIPTION         "<Definition> Kullanicinin islem yaptigi zamanin bilgisi. 
                            <Object Identifier> 1.3.6.1.4.1.59873.4.2.1.6.2.1.3
                            <Unit>  "
        ::= { kgm_userOperationsEntry 3} 
--1.6.2.1.4 kgm_userOperationsULoginName
    kgm_userOperationsULoginName OBJECT-TYPE
        SYNTAX              OCTET STRING
        ACCESS              read-only
        STATUS              mandatory
        DESCRIPTION         "<Definition> Islem yapan kullanicinin kullanici adi bilgisi.   
                            <Object Identifier> 1.3.6.1.4.1.59873.4.2.1.6.2.1.4
                            <Unit>  "
        ::= { kgm_userOperationsEntry 4}
--1.6.3 kgm_userListFileUpdate
    kgm_userListFileUpdate OBJECT-TYPE
        SYNTAX              INTEGER (0..1)
        ACCESS              read-only
        STATUS              mandatory
        DESCRIPTION         "<Definition>  
                                0 ise kullanici listesi guncellenemedi
                                1 ise kullanici listesi guncellendi
                            <Object Identifier> 1.3.6.1.4.1.59873.4.2.1.6.3
                            <Unit>  "
    ::= { kgm_user 3}
END
